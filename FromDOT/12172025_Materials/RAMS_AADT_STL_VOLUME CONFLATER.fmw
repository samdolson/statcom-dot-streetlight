FME workspace RAMS_AADT_STL_VOLUME CONFLATER.fmw

Parameters:
- SourceDataset_CSV2_3 = $(FME_MF_DIR)DATA\STL_EXTRACT\1990536_STATCOM1_2024_RAMP\1990536_STATCOM1_2024_RAMP\1990536_STATCOM1_2024_RAMP_ct_all.csv   # Source CSV (Comma Separated Value) File(s)
- SourceDataset_GEODATABASE_SDE = PRAMS.TDSOUT_SYSPLN QAQC   # ArcSDE Geodatabase Connection
- SourceDataset_SHAPEFILE_7 = $(FME_MF_DIR)DATA\STL_EXTRACT\1991984_STATCOM1_2022_MOTORWAY\1991984_STATCOM1_2022_MOTORWAY\Shapefile\1991984_STATCOM1_2022_MOTORWAY_osm_segment.shp   # Source Esri Shapefile(s)
- SourceDataset_SHAPEFILE_9 = $(FME_MF_DIR)DATA\STL_EXTRACT\1991985_STATCOM1_2022_RAMP\1991985_STATCOM1_2022_RAMP\Shapefile\1991985_STATCOM1_2022_RAMP_osm_segment.shp   # Source Esri Shapefile(s)
- SourceDataset_CSV2_7 = $(FME_MF_DIR)DATA\STL_EXTRACT\1991984_STATCOM1_2022_MOTORWAY\1991984_STATCOM1_2022_MOTORWAY\1991984_STATCOM1_2022_MOTORWAY_ct_all.csv   # Source CSV (Comma Separated Value) File(s)
- SourceDataset_CSV2_9 = $(FME_MF_DIR)DATA\STL_EXTRACT\1991985_STATCOM1_2022_RAMP\1991985_STATCOM1_2022_RAMP\1991985_STATCOM1_2022_RAMP_ct_all.csv   # Source CSV (Comma Separated Value) File(s)
- SourceDataset_SHAPEFILE_8 = $(FME_MF_DIR)DATA\STL_EXTRACT\1989473_STATCOM1_2024_MOTORWAY\1989473_STATCOM1_2024_MOTORWAY\Shapefile\1989473_STATCOM1_2024_MOTORWAY_osm_segment.shp   # Source Esri Shapefile(s)
- SourceDataset_SHAPEFILE_10 = $(FME_MF_DIR)DATA\STL_EXTRACT\1990536_STATCOM1_2024_RAMP\1990536_STATCOM1_2024_RAMP\Shapefile\1990536_STATCOM1_2024_RAMP_osm_segment\1990536_STATCOM1_2024_RAMP_osm_segment.shp   # Source Esri Shapefile(s)
- SourceDataset_CSV2 = $(FME_MF_DIR)DATA\STL_EXTRACT\1989473_STATCOM1_2024_MOTORWAY\1989473_STATCOM1_2024_MOTORWAY\1989473_STATCOM1_2024_MOTORWAY_ct_all.csv   # Source CSV (Comma Separated Value) File(s)
- DestDataset_SHAPEFILE = $(FME_MF_DIR)DATA\CONFLATED   # Destination Esri Shapefile Folder
- SourceDataset_GEODATABASE_SDE_3 = PRAMS.TDSOUT_SYSPLN QAQC   # ArcSDE Geodatabase Connection
- DestDataset_SHAPEFILE_2 = $(FME_MF_DIR)DATA\RAMS_EXPORT   # Destination Esri Shapefile Folder

Readers:
- CSV2_2: CSV2 from $(SourceDataset_CSV2_3)
- GEODATABASE_SDE_1: GEODATABASE_SDE from $(SourceDataset_GEODATABASE_SDE)
- SHAPEFILE_2: SHAPEFILE from $(SourceDataset_SHAPEFILE_7)
- SHAPEFILE_3: SHAPEFILE from $(SourceDataset_SHAPEFILE_9)
- CSV2_4: CSV2 from $(SourceDataset_CSV2_7)
- CSV2_5: CSV2 from $(SourceDataset_CSV2_9)
- SHAPEFILE_5: SHAPEFILE from $(SourceDataset_SHAPEFILE_8)
- SHAPEFILE_6: SHAPEFILE from $(SourceDataset_SHAPEFILE_10)
- CSV2_1: CSV2 from $(SourceDataset_CSV2)
- GEODATABASE_SDE_2: GEODATABASE_SDE from $(SourceDataset_GEODATABASE_SDE_3)

Writers:
- SHAPEFILE_1: SHAPEFILE to $(DestDataset_SHAPEFILE)
- SHAPEFILE_4: SHAPEFILE to $(DestDataset_SHAPEFILE_2)

MFT_STATCOM1_2024 (reader GEODATABASE_SDE_2)
    attributes: OBJECTID integer, ID char(38), ROUTEID char(15), FROMMEASURE double, TOMEASURE double, AADT integer, AADT_YEAR integer, DIRECTION char(1), SHAPE.LEN double
    -> TestFilter_4
    -> TDSOUT_SYSPLN.STATCOM1_2024 (writer SHAPEFILE_4)
AttributeManager_2
    ATTR_TABLE = RENAME_SET_VALUE AADT > AADT_IADOT (int32)
    -> FeatureJoiner [RIGHT]
TDSOUT_SYSPLN.STATCOM1_2024 (writer SHAPEFILE_4)
    attributes: OBJECTID long, ID varchar(38), ROUTEID varchar(15), FROMMEASUR double, TOMEASURE double, AADT long, AADT_YEAR long, DIRECTION varchar(1), SHAPE_LEN double
MFT_STATCOM1_2022 (reader GEODATABASE_SDE_1)
    attributes: OBJECTID integer, ID char(38), ROUTEID char(15), FROMMEASURE double, TOMEASURE double, AADT integer, AADT_YEAR integer, DIRECTION char(1), SHAPE.LEN double
    -> TestFilter_8
    -> TDSOUT_SYSPLN.STATCOM1_2022 (writer SHAPEFILE_4)
AttributeManager_6
    ATTR_TABLE = RENAME_SET_VALUE AADT > AADT_IADOT (int32)
    -> FeatureJoiner_5 [RIGHT]
AttributeManager_5
    ATTR_TABLE:
      REMOVE OBJECTID (int32)
      REMOVE ROUTEID (varchar(15))
      REMOVE FROMMEASURE (real64)
      REMOVE TOMEASURE (real64)
      REMOVE AADT (real64)
      REMOVE AADT_YEAR (int32)
      REMOVE DIRECTION (varchar(1))
      REMOVE SHAPE.LEN (real64)
    -> NeighborFinder_2 [CANDIDATE]
TDSOUT_SYSPLN.STATCOM1_2022 (writer SHAPEFILE_4)
    attributes: OBJECTID long, ID varchar(38), ROUTEID varchar(15), FROMMEASUR double, TOMEASURE double, AADT long, AADT_YEAR long, DIRECTION varchar(1), SHAPE_LEN double
Note: Divide into 100 points. First and last will be 1/101th from start and end
LineDivider
    DIM = 2D
    MODE = ToNumber
    OUTPUT = PointsExceptEndNodes
    VALUE = 101
    Point -> NeighborFinder [BASE]
Note: Find up to 10 pairs within 5m
NeighborFinder
    ATTR_ACCUM_MODE = Merge Candidate
    ATTR_CONFLICT_RES = Use Base
    CANDIDATES_FIRST = No
    INSERT_VERTEX = No
    K = 10
    MAX = 5
    MEASURES_FROM_CANDIDATE = Yes
    MEASURE_TYPE = Continuous
    MODE = Bases and Candidates
    TREAT_POLYGON_AS = Lines
    MATCHED -> StatisticsCalculator
    <REJECTED> -> Logger
Note: Divide into 100 points. First and last will be 1/101th from start and end
LineDivider_2
    DIM = 2D
    MODE = ToNumber
    OUTPUT = PointsExceptEndNodes
    VALUE = 101
    Point -> NeighborFinder_2 [BASE]
Note: Find up to 10 pairs within 5m
NeighborFinder_2
    ATTR_ACCUM_MODE = Merge Candidate
    ATTR_CONFLICT_RES = Use Base
    CANDIDATES_FIRST = No
    INSERT_VERTEX = No
    K = 10
    MAX = 5
    MEASURES_FROM_CANDIDATE = Yes
    MEASURE_TYPE = Continuous
    MODE = Bases and Candidates
    TREAT_POLYGON_AS = Lines
    MATCHED -> StatisticsCalculator_2
    <REJECTED> -> Logger_2
AttributeManager_10
    ATTR_TABLE:
      REMOVE name (varchar(53))
      REMOVE ID.total_count (uint64)
    -> 2024 (writer SHAPEFILE_1)
AttributeManager_9
    ATTR_TABLE:
      REMOVE name (varchar(53))
      REMOVE ID.total_count (uint64)
    -> 2022 (writer SHAPEFILE_1)

Bookmark: Halve the AADT on Non-ramps, re-project,remove NULLs
TestFilter_4
    DEFAULT_VALUE = <UNFILTERED>
    PASSED_TEST_GROUP_OUTPUT = FIRST
    TEST_LIST = "BOOL_OP,OR,COMPOSITE_TEST,""""""1"""""",TEST_CLAUSE,TEST @Evaluate(@StringLength(@Value(ROUTEID))) = 11",@Evaluate(@Length(@Value(ROUTEID))) != 11
    @Evaluate(@Length(@Value(ROUTEID))) != 11 -> AttributeManager_4
    <UNFILTERED> -> Reprojector_3
AttributeManager_4
    ATTR_TABLE = SET_TO AADT (real64) = @Evaluate(@Value(AADT)/2)
    -> Reprojector_3
Reprojector_3
    DEST = UTM84-15N
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> TestFilter
TestFilter
    DEFAULT_VALUE = <UNFILTERED>
    PASSED_TEST_GROUP_OUTPUT = FIRST
    TEST_LIST = "BOOL_OP,AND,COMPOSITE_TEST,""""""1"""""",TEST_CLAUSE,TEST AADT_YEAR ATTRIBUTE_HAS_A_VALUE """,AADT_YEAR ATTRIBUTE_HAS_A_VALUE
    AADT_YEAR ATTRIBUTE_HAS_A_VALUE -> NeighborFinder [CANDIDATE]
    AADT_YEAR ATTRIBUTE_HAS_A_VALUE -> AttributeManager_2

Bookmark: Halve the AADT on Non-ramps, re-project,remove NULLs
TestFilter_8
    DEFAULT_VALUE = <UNFILTERED>
    PASSED_TEST_GROUP_OUTPUT = FIRST
    TEST_LIST = "BOOL_OP,OR,COMPOSITE_TEST,""""""1"""""",TEST_CLAUSE,TEST @Evaluate(@StringLength(@Value(ROUTEID))) = 11",@Evaluate(@Length(@Value(ROUTEID))) != 11
    @Evaluate(@Length(@Value(ROUTEID))) != 11 -> AttributeManager_8
    <UNFILTERED> -> Reprojector_5
AttributeManager_8
    ATTR_TABLE = SET_TO AADT (real64) = @Evaluate(@Value(AADT)/2)
    -> Reprojector_5
Reprojector_5
    DEST = UTM84-15N
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> TestFilter_5
TestFilter_5
    DEFAULT_VALUE = <UNFILTERED>
    PASSED_TEST_GROUP_OUTPUT = FIRST
    TEST_LIST = "BOOL_OP,AND,COMPOSITE_TEST,""""""1"""""",TEST_CLAUSE,TEST AADT_YEAR ATTRIBUTE_HAS_A_VALUE """,AADT_YEAR ATTRIBUTE_HAS_A_VALUE
    AADT_YEAR ATTRIBUTE_HAS_A_VALUE -> AttributeManager_5
    AADT_YEAR ATTRIBUTE_HAS_A_VALUE -> AttributeManager_6

Bookmark: Import STL OSM (Ramps and Motorways)
1989473_STATCOM1_2024_MOTORWAY_osm_segment (reader SHAPEFILE_5)
    attributes: segment_id number(19,0), name varchar(53), segment_ty varchar(8)
    -> Reprojector_2
1990536_STATCOM1_2024_RAMP_osm_segment (reader SHAPEFILE_6)
    attributes: segment_id number(19,0), name varchar(66), segment_ty varchar(8)
    -> Reprojector_2
Reprojector_2
    DEST = UTM84-15N
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> LineDivider [Line]
    REPROJECTED -> FeatureJoiner_3 [RIGHT]

Bookmark: Determine OSM segments where at least %98 of length is within 5m of *ONE* RAMS routeID, Elimitate OSM segments where that relationship is not unique
StatisticsCalculator
    ATTR_ACCUM_MODE = None
    CALCULATION_MODE = NUMERIC
    FEAT_STATS = ID,NUMERIC_MODE,,,COUNT,,,,,,,,,,
    GROUP_BY = ID name
    SUMMARY -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(ID.total_count) >= 98",Mets threshold
    Mets threshold -> DuplicateFilter
DuplicateFilter
    INPUT_ORDERED_CHOICE_LOOKUP = NO
    KEYATTR = ID
    INPUT_ORDERED_CHOICE = No
    UNIQUE -> FeatureJoiner_4 [LEFT]
    DUPLICATE -> FeatureJoiner_4 [RIGHT]
FeatureJoiner_4
    ATTR_CONFLICT_RES_LOOKUP = USE_LEFT
    GEOMETRY_HANDLING_LOOKUP = USE_LEFT
    JOIN_KEYS = ID ID AUTO
    JOIN_MODE = Inner
    ATTR_CONFLICT_RES = Prefer Left
    GEOMETRY_HANDLING = Prefer Left
    UNJOINED_LEFT -> FeatureJoiner [LEFT]

Bookmark: Join, Join, Join
FeatureJoiner
    ATTR_CONFLICT_RES_LOOKUP = USE_LEFT
    GEOMETRY_HANDLING_LOOKUP = USE_RIGHT
    JOIN_KEYS = ID ID AUTO
    JOIN_MODE = Inner
    ATTR_CONFLICT_RES = Prefer Left
    GEOMETRY_HANDLING = Prefer Right
    JOINED -> FeatureJoiner_2 [LEFT]
FeatureJoiner_2
    ATTR_CONFLICT_RES_LOOKUP = USE_LEFT
    GEOMETRY_HANDLING_LOOKUP = USE_LEFT
    JOIN_KEYS = name Zone Name AUTO
    JOIN_MODE = Inner
    ATTR_CONFLICT_RES = Prefer Left
    GEOMETRY_HANDLING = Prefer Left
    JOINED -> FeatureJoiner_3 [LEFT]
FeatureJoiner_3
    ATTR_CONFLICT_RES_LOOKUP = USE_LEFT
    GEOMETRY_HANDLING_LOOKUP = USE_RIGHT
    JOIN_KEYS = name name AUTO
    JOIN_MODE = Inner
    ATTR_CONFLICT_RES = Prefer Left
    GEOMETRY_HANDLING = Prefer Right
    JOINED -> AttributeManager_10
    JOINED -> Inspector

Bookmark: Errors, NBD
Logger
    LOG_FEATURE = LOG_ONLY
    MAXCOORDS = 20
    MAXFEATS = 20
    MESSAGE = Feature is:
    SEVERITY = INFO

Bookmark: Import STL OSM (Ramps and Motorways)
1991984_STATCOM1_2022_MOTORWAY_osm_segment (reader SHAPEFILE_2)
    attributes: segment_id number(19,0), name varchar(53), segment_ty varchar(8)
    -> Reprojector_4
1991985_STATCOM1_2022_RAMP_osm_segment (reader SHAPEFILE_3)
    attributes: segment_id number(19,0), name varchar(66), segment_ty varchar(8)
    -> Reprojector_4
Reprojector_4
    DEST = UTM84-15N
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> LineDivider_2 [Line]
    REPROJECTED -> FeatureJoiner_7 [RIGHT]

Bookmark: Determine OSM segments where at least %98 of length is within 5m of *ONE* RAMS routeID, Elimitate OSM segments where that relationship is not unique
StatisticsCalculator_2
    ATTR_ACCUM_MODE = None
    CALCULATION_MODE = NUMERIC
    FEAT_STATS = ID,NUMERIC_MODE,,,COUNT,,,,,,,,,,
    GROUP_BY = ID name
    SUMMARY -> TestFilter_6
TestFilter_6
    DEFAULT_VALUE = <UNFILTERED>
    PASSED_TEST_GROUP_OUTPUT = FIRST
    TEST_LIST = "BOOL_OP,OR,COMPOSITE_TEST,""""""1"""""",TEST_CLAUSE,TEST @Value(ID.total_count) >= 98",Mets threshold
    Mets threshold -> DuplicateFilter_2
DuplicateFilter_2
    INPUT_ORDERED_CHOICE_LOOKUP = NO
    KEYATTR = ID
    INPUT_ORDERED_CHOICE = No
    UNIQUE -> FeatureJoiner_8 [LEFT]
    DUPLICATE -> FeatureJoiner_8 [RIGHT]
FeatureJoiner_8
    ATTR_CONFLICT_RES_LOOKUP = USE_LEFT
    GEOMETRY_HANDLING_LOOKUP = USE_LEFT
    JOIN_KEYS = ID ID AUTO
    JOIN_MODE = Inner
    ATTR_CONFLICT_RES = Prefer Left
    GEOMETRY_HANDLING = Prefer Left
    UNJOINED_LEFT -> FeatureJoiner_5 [LEFT]

Bookmark: Join, Join, Join
FeatureJoiner_5
    ATTR_CONFLICT_RES_LOOKUP = USE_LEFT
    GEOMETRY_HANDLING_LOOKUP = USE_RIGHT
    JOIN_KEYS = ID ID AUTO
    JOIN_MODE = Inner
    ATTR_CONFLICT_RES = Prefer Left
    GEOMETRY_HANDLING = Prefer Right
    JOINED -> FeatureJoiner_6 [LEFT]
FeatureJoiner_6
    ATTR_CONFLICT_RES_LOOKUP = USE_LEFT
    GEOMETRY_HANDLING_LOOKUP = USE_LEFT
    JOIN_KEYS = name Zone Name AUTO
    JOIN_MODE = Inner
    ATTR_CONFLICT_RES = Prefer Left
    GEOMETRY_HANDLING = Prefer Left
    JOINED -> FeatureJoiner_7 [LEFT]
FeatureJoiner_7
    ATTR_CONFLICT_RES_LOOKUP = USE_LEFT
    GEOMETRY_HANDLING_LOOKUP = USE_RIGHT
    JOIN_KEYS = name name AUTO
    JOIN_MODE = Inner
    ATTR_CONFLICT_RES = Prefer Left
    GEOMETRY_HANDLING = Prefer Right
    JOINED -> AttributeManager_9
    JOINED -> Inspector_2

Bookmark: Errors, NBD
Logger_2
    LOG_FEATURE = LOG_ONLY
    MAXCOORDS = 20
    MAXFEATS = 20
    MESSAGE = Feature is:
    SEVERITY = INFO

Bookmark: Import STL Data (Ramps and Motorways)
CSV (reader CSV2_1)
    attributes: Data Periods varchar(27), Mode of Travel varchar(38), Zone ID varchar(1), Zone Name varchar(53), Road Class varchar(8), Line Zone Length (Miles) real32, Zone Is Pass-Through varchar(3), Zone Direction (degrees) uint32, Zone is Bi-Direction varchar(3), Day Type varchar(22), Day Part varchar(23), Average Daily Segment Traffic (StL Volume) uint32, Avg Segment Speed (mph) uint32, Avg Segment Travel Time (sec) uint32, Free Flow Speed (mph) real32, Vehicle Miles of Travel (StL Volume) real64, Vehicle Hours of Delay (StL Volume) varchar(6), Travel Time Index real32, Buffer Index varchar(6), Planning Time Index varchar(6), Level of Travel Time Reliability varchar(5), Reliable Segment? varchar(5), 80th Travel Time Index varchar(5), 90th Travel Time Index varchar(5), 5th Speed Percentile varchar(3), 10th Speed Percentile varchar(3), 20th Speed Percentile varchar(3), 50th Speed Percentile varchar(3)
    -> TestFilter_2
CSV (reader CSV2_2)
    attributes: Data Periods varchar(27), Mode of Travel varchar(38), Zone ID varchar(1), Zone Name varchar(66), Road Class varchar(11), Line Zone Length (Miles) real32, Zone Is Pass-Through varchar(3), Zone Direction (degrees) uint32, Zone is Bi-Direction varchar(3), Day Type varchar(22), Day Part varchar(23), Average Daily Segment Traffic (StL Volume) uint32, Avg Segment Speed (mph) varchar(3), Avg Segment Travel Time (sec) varchar(3), Free Flow Speed (mph) real32, Vehicle Miles of Travel (StL Volume) real32, Vehicle Hours of Delay (StL Volume) varchar(5), Travel Time Index real32, Buffer Index varchar(6), Planning Time Index varchar(6), Level of Travel Time Reliability varchar(6), Reliable Segment? varchar(5), 80th Travel Time Index varchar(6), 90th Travel Time Index varchar(6), 5th Speed Percentile varchar(3), 10th Speed Percentile varchar(3), 20th Speed Percentile varchar(3), 50th Speed Percentile varchar(3)
    -> TestFilter_2
TestFilter_2
    DEFAULT_VALUE = <UNFILTERED>
    PASSED_TEST_GROUP_OUTPUT = FIRST
    TEST_LIST:
      "BOOL_OP,AND,COMPOSITE_TEST,""""""1 AND 2"""""",TEST_CLAUSE,TEST @Value(Day Part) = 00: All Day (12am-12am)
      TEST @Value(Day Type) = 0: All Days (M-Su)",@Value(Day Part) = 00: All Day (12am-12am)
    @Value(Day Part) = 00: All Day (12am-12am) -> AttributeManager_3
AttributeManager_3
    ATTR_TABLE:
      REMOVE Data Periods (varchar(27))
      REMOVE Mode of Travel (varchar(38))
      REMOVE Zone ID (varchar(1))
      REMOVE Road Class (varchar(8))
      REMOVE Line Zone Length (Miles) (real32)
      REMOVE Zone Is Pass-Through (varchar(3))
      REMOVE Zone Direction (degrees) (uint32)
      REMOVE Zone is Bi-Direction (varchar(3))
      REMOVE Day Type (varchar(22))
      REMOVE Day Part (varchar(23))
      RENAME_SET_VALUE Average Daily Segment Traffic (StL Volume) > VOLUME_STL (uint32)
      REMOVE Avg Segment Speed (mph) (uint32)
      REMOVE Avg Segment Travel Time (sec) (uint32)
      REMOVE Free Flow Speed (mph) (real32)
      REMOVE Vehicle Miles of Travel (StL Volume) (real64)
      REMOVE Vehicle Hours of Delay (StL Volume) (varchar(6))
      REMOVE Travel Time Index (real32)
      REMOVE Buffer Index (varchar(6))
      REMOVE Planning Time Index (varchar(6))
      REMOVE Level of Travel Time Reliability (varchar(5))
      REMOVE Reliable Segment? (varchar(5))
      REMOVE 80th Travel Time Index (varchar(5))
      REMOVE 90th Travel Time Index (varchar(5))
      REMOVE 5th Speed Percentile (varchar(3))
      REMOVE 10th Speed Percentile (varchar(3))
      REMOVE 20th Speed Percentile (varchar(3))
      REMOVE 50th Speed Percentile (varchar(3))
    -> FeatureJoiner_2 [RIGHT]

Bookmark: Export
Inspector
2024 (writer SHAPEFILE_1)
    attributes: ID varchar(38), OBJECTID long, ROUTEID varchar(15), FROMMEASUR double, TOMEASURE double, AADT_IADOT long, AADT_YEAR long, DIRECTION varchar(1), SHAPE_LEN double, Zone Name varchar(66), VOLUME_STL double, segment_id number(19,0), segment_ty varchar(8)

Bookmark: Import STL Data (Ramps and Motorways)
CSV (reader CSV2_4)
    attributes: Data Periods varchar(27), Mode of Travel varchar(38), Zone ID varchar(1), Zone Name varchar(53), Road Class varchar(8), Line Zone Length (Miles) real32, Zone Is Pass-Through varchar(3), Zone Direction (degrees) uint32, Zone is Bi-Direction varchar(3), Day Type varchar(22), Day Part varchar(23), Average Daily Segment Traffic (StL Volume) uint32, Avg Segment Speed (mph) uint32, Avg Segment Travel Time (sec) uint32, Free Flow Speed (mph) real32, Vehicle Miles of Travel (StL Volume) real64, Vehicle Hours of Delay (StL Volume) varchar(6), Travel Time Index real32, Buffer Index varchar(6), Planning Time Index varchar(6), Level of Travel Time Reliability varchar(5), Reliable Segment? varchar(5), 80th Travel Time Index varchar(5), 90th Travel Time Index varchar(5), 5th Speed Percentile varchar(3), 10th Speed Percentile varchar(3), 20th Speed Percentile varchar(3), 50th Speed Percentile varchar(3)
    -> TestFilter_7
CSV (reader CSV2_5)
    attributes: Data Periods varchar(27), Mode of Travel varchar(38), Zone ID varchar(1), Zone Name varchar(66), Road Class varchar(11), Line Zone Length (Miles) real32, Zone Is Pass-Through varchar(3), Zone Direction (degrees) uint32, Zone is Bi-Direction varchar(3), Day Type varchar(22), Day Part varchar(23), Average Daily Segment Traffic (StL Volume) uint32, Avg Segment Speed (mph) varchar(3), Avg Segment Travel Time (sec) varchar(3), Free Flow Speed (mph) real32, Vehicle Miles of Travel (StL Volume) real32, Vehicle Hours of Delay (StL Volume) varchar(5), Travel Time Index real32, Buffer Index varchar(6), Planning Time Index varchar(6), Level of Travel Time Reliability varchar(6), Reliable Segment? varchar(5), 80th Travel Time Index varchar(6), 90th Travel Time Index varchar(6), 5th Speed Percentile varchar(3), 10th Speed Percentile varchar(3), 20th Speed Percentile varchar(3), 50th Speed Percentile varchar(3)
    -> TestFilter_7
TestFilter_7
    DEFAULT_VALUE = <UNFILTERED>
    PASSED_TEST_GROUP_OUTPUT = FIRST
    TEST_LIST:
      "BOOL_OP,AND,COMPOSITE_TEST,""""""1 AND 2"""""",TEST_CLAUSE,TEST @Value(Day Part) = 00: All Day (12am-12am)
      TEST @Value(Day Type) = 0: All Days (M-Su)",@Value(Day Part) = 00: All Day (12am-12am)
    @Value(Day Part) = 00: All Day (12am-12am) -> AttributeManager_7
AttributeManager_7
    ATTR_TABLE:
      REMOVE Data Periods (varchar(27))
      REMOVE Mode of Travel (varchar(38))
      REMOVE Zone ID (varchar(1))
      REMOVE Road Class (varchar(8))
      REMOVE Line Zone Length (Miles) (real32)
      REMOVE Zone Is Pass-Through (varchar(3))
      REMOVE Zone Direction (degrees) (uint32)
      REMOVE Zone is Bi-Direction (varchar(3))
      REMOVE Day Type (varchar(22))
      REMOVE Day Part (varchar(23))
      RENAME_SET_VALUE Average Daily Segment Traffic (StL Volume) > VOLUME_STL (uint32)
      REMOVE Avg Segment Speed (mph) (uint32)
      REMOVE Avg Segment Travel Time (sec) (uint32)
      REMOVE Free Flow Speed (mph) (real32)
      REMOVE Vehicle Miles of Travel (StL Volume) (real64)
      REMOVE Vehicle Hours of Delay (StL Volume) (varchar(6))
      REMOVE Travel Time Index (real32)
      REMOVE Buffer Index (varchar(6))
      REMOVE Planning Time Index (varchar(6))
      REMOVE Level of Travel Time Reliability (varchar(5))
      REMOVE Reliable Segment? (varchar(5))
      REMOVE 80th Travel Time Index (varchar(5))
      REMOVE 90th Travel Time Index (varchar(5))
      REMOVE 5th Speed Percentile (varchar(3))
      REMOVE 10th Speed Percentile (varchar(3))
      REMOVE 20th Speed Percentile (varchar(3))
      REMOVE 50th Speed Percentile (varchar(3))
    -> FeatureJoiner_6 [RIGHT]

Bookmark: Export
Inspector_2
2022 (writer SHAPEFILE_1)
    attributes: ID varchar(38), OBJECTID long, ROUTEID varchar(15), FROMMEASUR double, TOMEASURE double, AADT_IADOT long, AADT_YEAR long, DIRECTION varchar(1), SHAPE_LEN double, Zone Name varchar(53), VOLUME_STL double, segment_id number(19,0), segment_ty varchar(8)

FME custom transformer LineDivider
Divides a line into multiple lines. Resulting lines and/or points which separate the lines will be output.
Every output feature will hold all the attributes of the original feature.
This transformer accepts non-aggregate Curve (Line, Arc or Path) features only.
If an input feature has other type geometry or does not have geometry, it will be output from the <Rejected> port.
Similar functions have been provided by the IterativeSnipper_2013 and the DistanceMarker_2013 in the FME Hub.
Major differences from them are:
1) Integrated their functions so that divided lines and distance markers can be created efficiently at the same time, but users still can also use each function separately. See the "Output" parameter.
2) Added "Measurement Mode" parameter so that users can choose 2D or 3D for measuring lengths.
3) Implemented with a Python script to improve performance, although the algorithm is basically same as theirs.
Parameters
Measurement Mode:
By default, the transformer measures lengths in 2D, but you can change it to 3D with this parameter setting.
Dividing Mode:
Choose one of these modes.
"Shorten to Following Length"
- snips iteratively each input line from its head by the length specified to the "Line Length or Number of Lines" parameter. Length of the final line could be less than the specified length.
"Shorten to Approximately Following Length"
- divides each input line into multiple lines having identical length which is approximately equal to the length specified to the "Line Length or Number of Lines" parameter.
"Divide to Following Number of Lines"
- divides each input line into multiple lines having identical length by the number specified to the "Line Length or Number of Lines" parameter.
Line Length or Number of Lines:
Specify a numeric value if you set "Shorten to Following Length" or "Shorten to Approximately Following Length" in the "Dividing Mode" parameter.
Specify an integer number if you set "Divide to Following Number of Lines" in the "Dividing Mode" parameter.
In both cases, the value must be greater than 0.
Output:
You can control what kind of features should be output with this parameter setting.
By default, the transformer outputs both Lines and Points, but you could run it more efficiently by selecting a preferable option if you need either only Lines or Points.
"Lines"
- outputs divided lines only. Nothing is output from the Point port.
"Lines and Points" (default)
- outputs both divided lines and points which separate the lines; including start and end nodes of the original line.
"Lines and Points except Start and End Nodes"
- outputs both divided lines and points which separate the lines; excluding start and end nodes of the original line.
"Points"
- outputs points only; including start and end nodes of the original line. Nothing is output from the Line port.
"Points except Start and End Nodes"
- outputs points only; excluding start and end nodes of the original line. Nothing is output from the Line port.

Parameters:
- DIM = 2D   # Measurement Mode
- MODE = ToLength
- VALUE =   # Line Length or Number of Lines
- OUTPUT = LinesAndPoints

Line (input)
    -> AggregateFilter
AggregateFilter
    AGGREGATE -> <Rejected> (output)
    NOT_AGGREGATE -> GeometryFilter
GeometryFilter
    BREAK_AGG_BOOL = 0
    GEOM_PORTS = LINE ARC
    BREAK_AGG = No
    GEOM_PORT_NAMES = Line Arc
    LINE -> AttributeCreator
    ARC -> AttributeCreator
    <UNFILTERED> -> <Rejected> (output)
AttributeCreator
    ATTR_LIST = __linedivider.dim,$(DIM),__linedivider.mode,$(MODE),__linedivider.value,@Evaluate($(VALUE)),__linedivider.output,$(OUTPUT)
    -> PythonCaller
PythonCaller
    HIDE_ATTRIBUTES = __linedivider.dim __linedivider.mode __linedivider.value __linedivider.output
    PYTHONSOURCE:
      # 2014-11-15, Takashi Iijima, Original Implementation
      # 2015-05-11, Takashi Iijima, Added Arc support; Fixed a problem on creating interval points of Path
      # 2017-06-26, Takashi Iijima, Updated to improve robustness.
      # 2020-01-12, Takashi Iijima, Changed Default Python Interpreter to 3.6+, saved with FME 2017.1.2.1

      import fmeobjects, math

      class LineDivider(object):
          def input(self, feature):
              is3D = (feature.getAttribute('__linedivider.dim') == '3D')
              mode = feature.getAttribute('__linedivider.mode')
              value = float(feature.getAttribute('__linedivider.value'))
              output = feature.getAttribute('__linedivider.output')
              for attr in ['dim', 'mode', 'value', 'output']:
                  feature.removeAttribute('__linedivider.' + attr)

              coordSys = feature.getCoordSys()
              outputLines = output.startswith('Lines')
              outputPoints = output.startswith('LinesAndPoints') or output.startswith('Points')
              outputEndNodes = outputPoints and not output.endswith('ExceptEndNodes')

              # Get original curve geometry
              curve = feature.getGeometry()
              length = curve.getLength(is3D)
              numLines = int(round(value) if mode == 'ToNumber' else math.ceil(length / value))
              len = value if mode == 'ToLength' else length / numLines

              for n, (beg, end) in enumerate([(i*len, (i+1)*len) for i in range(numLines)], 1):
                  # Snip the original curve
                  if n == numLines:
                      end = -1
                  curve.snip(fmeobjects.SNIP_DISTANCE, is3D, beg, end)

                  if outputLines:
                      line = feature.cloneAttributes()
                      line.setGeometry(curve)
                      line.setCoordSys(coordSys)
                      self.pyoutput(line)

                  if outputPoints and (0.0 < beg or outputEndNodes):
                      point = feature.cloneAttributes()
                      point.setGeometry(curve.getStartPoint())
                      point.setCoordSys(coordSys)
                      self.pyoutput(point)

                  # Restore original curve geometry
                  curve = feature.getGeometry()

              if outputEndNodes:
                  point = feature.cloneAttributes()
                  point.setGeometry(curve.getEndPoint())
                  point.setCoordSys(coordSys)
                  self.pyoutput(point)
    PYTHONSYMBOL = LineDivider
    -> GeometryFilter_2
GeometryFilter_2
    BREAK_AGG_BOOL = 0
    GEOM_PORTS = POINT LINE ARC
    BREAK_AGG = No
    GEOM_PORT_NAMES = Point Line Arc
    POINT -> Point (output)
    LINE -> Line (output)
    ARC -> Line (output)
Line (output)
Point (output)
<Rejected> (output)
